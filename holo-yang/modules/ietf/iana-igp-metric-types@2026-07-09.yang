module iana-igp-metric-types {
  yang-version 1.1;
  namespace "urn:ietf:params:xml:ns:yang:iana-igp-metric-types";
  prefix iana-metric-types;

  organization
    "Internet Assigned Numbers Authority (IANA)";
  contact
    "Internet Assigned Numbers Authority

     ICANN
     12025 Waterfront Drive, Suite 300
     Los Angeles, CA 90094-2536
     United States of America

     Tel:    +1 310 301 5800
      <mailto:iana@iana.org>";
  description
    "The YANG module defines the YANG data types for IANA-registered
     Interior Gateway Protocol (IGP) Metric-Types.

     This YANG module is maintained by IANA and reflects the 'IGP
     Metric-Type' registry.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This initial version of this YANG module is part of RFC XXXX
     (https://www.rfc-editor.org/info/rfcXXXX); see the RFC itself
     for full legal notices.

     //RFC Ed.: replace XXXX with actual RFC number and remove
       this note

     The latest version of this YANG module is available at
     https://www.iana.org/assignments/yang-parameters.";

  reference
    "Interior Gateway Protocol (IGP) Parameters, IGP Metric-Type
     (https://www.iana.org/assignments/igp-parameters/
      igp-parameters.xhtml#igp-metric-type)";

  revision 2026-07-09 {
    description
      "Initial Version";
    reference
      "RFC XXXX: A YANG Data Model for OSPF Application-Specific
                 Link Attributes and Flexible Algorithm";
  }

  typedef metric-type {
    type enumeration {
      enum igp-metric {
        value 0;
        description
          "IGP Metric.";
        reference
          "RFC9350: IGP Flexible Algorithm, Section 5.1";
      }

      enum min-unidirectional-link-delay {
        value 1;
        description
          "Min Unidirectional Link Delay as defined in RFC 8570
           and RFC 7471 Section 4.2.";
        reference
          "RFC 9350: IGP Flexible Algorithm, Section 5.1";
      }

      enum te-default-metric {
        value 2;
        description
          "Traffic Engineering Default Metric as defined in RFC 5305
           Section 3.7 and Traffic Engineering Metric as defined in
           RFC3630, Section 2.5.5.";
        reference
          "RFC 9350: IGP Flexible Algorithm, Section 5.1";
      }

      enum bandwidth-metric {
        value 3;
        description
          "Bandwidth metric.";
        reference
          "RFC 9843: IGP Flexible Algorithms: Bandwidth, Delay,
           Metrics, and Constraints";
      }
    }
    default "igp-metric";
    description
      "IGP Metric-Type. The metric types
       are defined in IANA IGP Metric-Type registry.";
  }
}
