module ietf-isis-link-attr {
  yang-version 1.1;
  namespace "urn:ietf:params:xml:ns:yang:ietf-isis-link-attr";
  prefix isis-link-attr;

  import ietf-inet-types {
    prefix inet;
    reference
      "RFC 9911: Common YANG Data Types";
  }
  import ietf-routing {
    prefix rt;
    reference
      "RFC 8349: A YANG Data Model for Routing
                 Management (NMDA Version)";
  }
  import ietf-isis {
    prefix isis;
    reference
      "RFC 9130: YANG Data Model for the IS-IS Protocol";
  }
  import ietf-routing-types {
    prefix rt-types;
    reference
      "RFC 8294: Common YANG Data Types for the
       Routing Area";
  }
  import ietf-te-types {
    prefix te-types;
    reference
      "RFC 8776: Common YANG Data Types for Traffic Engineering";
  }
  import iana-igp-link-attr-apps {
    prefix iana-link-attr-apps;
    reference
      "IANA IGP Link-Attribute Application Identifiers registry,
       <https://www.iana.org/assignments/igp-parameters>.";
  }

  organization
    "IETF LSR - Link State Routing Working Group";
  contact
    "WG Web:   <https://datatracker.ietf.org/wg/lsr>
     WG List:  <mailto:lsr@ietf.org>

     Author:   Yingzhen Qu
               <mailto:yingzhen.ietf@gmail.com>
     Author:   Acee Lindem
               <mailto:acee.ietf@gmail.com>
     Author:   Madhavi Joshi
               <mailto:madhavi@arrcus.com>
    ";
  description
    "This YANG module defines the configuration and operational
     state for IS-IS application specific link attributes feature as
     defined in RFC 9479.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (http://trustee.ietf.org/license-info).

     All revisions of IETF and IANA published modules can be found
     at the YANG Parameters registry group
     (https://www.iana.org/assignments/yang-parameters).
     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-07-11 {
    description
      "Initial version";
    reference
      "RFC XXXX: A YANG Data Model for IS-IS Application-Specific
                 Link Attributes and Flexible Algorithm";
  }

  typedef attr-advertise-mode {
    type enumeration {
      enum legacy {
        value 0;
        description
          "Only send legacy advertisements, and no ASLA
           advertisement. Legacy advertisements will be
           used for the application.";
      }
      enum app-specific {
        value 1;
        description
          "Application-specific advertisements are sent
           and used with L-flag clear.";
      }
      enum transition {
        value 2;
        description
          "Send both application-specific and legacy
           advertisements. Either application-specific or
           legacy attribute advertisements can be used
           by the application.";
      }
    }
    default "legacy";
    description
      "Link attributes operation mode.";
    reference
      "RFC 9479 - IS-IS Application-Specific Link Attributes,
       Section 6.3.";
  }
  grouping isis-te-link-attrs {
    description
      "IS-IS Application-Specific Link Attributes (ASLA)
       inherited from the base IS-IS TE attributes";
    leaf te-metric {
      type te-types:te-metric;
      description
        "TE default metric.";
      reference
        "RFC 5305: IS-IS Extensions for Traffic Engineering,
         Section 3.7";
    }
    leaf admin-group {
      type te-types:admin-group;
      description
        "Administrative Group / Resource Class/Color.";
      reference
        "RFC 5305: IS-IS Extensions for Traffic Engineering,
         Section 3.1";
    }
    leaf max-bandwidth {
      type rt-types:bandwidth-ieee-float32;
      units "bytes per second";
      description
        "Maximum bandwidth.";
      reference
        "RFC 5305: IS-IS Extensions for Traffic Engineering,
         Section 3.4";
    }
    leaf max-reservable-bandwidth {
      type rt-types:bandwidth-ieee-float32;
      units "bytes per second";
      description
        "Maximum reservable bandwidth.";
      reference
        "RFC 5305: IS-IS Extensions for Traffic Engineering,
         Section 3.5";
    }
    container unreserved-bandwidths {
      description
        "All unreserved bandwidths.";
      list unreserved-bandwidth {
        leaf priority {
          type uint8 {
            range "0..7";
          }
          description
            "Priority from 0 to 7. There should only be a single
             unreserved-bandwidth per priority.";
        }
        leaf unreserved-bandwidth {
          type rt-types:bandwidth-ieee-float32;
          units "bytes per second";
          description
            "Unreserved bandwidth.";
        }
        description
          "List of unreserved bandwidths for different
           priorities.";
      }
      reference
        "RFC 5305: IS-IS Extensions for Traffic Engineering,
         Section 3.6";
    }
    reference
      "RFC 5305: IS-IS Extensions for Traffic Engineering";
  }

  grouping application-identifier-bit-mask {
    description
      "Identification of the set of applications associated with
       link attribute advertisements";
    leaf l-flag {
      type boolean;
      description
        "Legacy Flag. When the SABM Length or UDABM Length is
         non-zero and the L-flag is not set, all applications
         specified in the bit mask use the link
         attribute advertisements in the sub-TLV.";
      reference
        "RFC 9479: IS-IS Application-Specific Link Attributes,
         Section 3";
    }
    container sabm {
      leaf-list sabm-bit {
        type iana-link-attr-apps:igp-link-attr-app;
        description
          "Standard Application Identifier Bit Mask bits. This
           leaf-list contains identities for the bits which are
           set to 1 in the SABM field.";
      }
      description
        "Standard Application Identifier Bit Mask.";
    }
    container udabm {
      description
        "User Defined Application Identifier Bit Mask (UDABM).
         This container is intended to be augmented by documents
         defining user-defined application identifiers.  Each
         such augmentation SHOULD add a leaf-list of identityref
         type whose base identity represents the user-defined
         application, following the same pattern as the
         'sabm-bit' leaf-list.  Refer to RFC 9479, Section 3
         for the on-wire encoding of the UDABM field.";
      reference
        "RFC 9479: IS-IS Application-Specific Link Attributes,
         Section 3";
    }
  }

  grouping application-specific-link-attributes-sub-tlv {
    description
      "Grouping for specification of the applications and
       application-specific attribute values.";
    container asla-sub-tlvs {
      list asla-sub-tlv {
        uses application-identifier-bit-mask;
        uses isis-te-link-attrs;
        uses isis:neighbor-extended-te-extensions;
        uses isis:unknown-tlvs;
        description
          "List of application specific link attributes sub-tlvs.";
      }
      description
        "Application specific link attributes sub-tlv.";
    }
  }

  grouping application-specific-srlg-tlv {
    description
      "Grouping of a TLV to advertise application-specific
       SRLGs for a given link.";
    container application-specific-srlg-tlv {
      list as-srlg-tlv {
        leaf neighbor-system-id {
          type isis:system-id;
          description
            "Neighbor System-ID.";
        }
        leaf pseudo-node-id {
          type uint8;
          description
            "Pseudo-node ID.";
        }
        uses application-identifier-bit-mask;
        container link-id-sub-tlvs {
          description
            "Link Identifier sub-TLVs.";
          container link-local-remote-ids {
            description
              "Link local/remote identifiers sub-tlv.";
            leaf link-local-id {
              type uint32;
              description
                "Local identifier of the link.";
            }
            leaf link-remote-id {
              type uint32;
              description
                "Remote identifier of the link. If the Link
                 Remote Identifier is unknown, it is set to 0.";
            }
          }
          container ipv4-interface-addr {
            leaf ipv4-int-addr {
              type inet:ipv4-address;
              description
                "IPv4 address for the interface.";
            }
            description
              "IPv4 interface address sub-tlv.";
          }
          container ipv4-neighbor-addr {
            leaf ipv4-neighbor-addr {
              type inet:ipv4-address;
              description
                "IPv4 address for a neighboring router
                 on this link.";
            }
            description
              "IPv4 neighbor address sub-tlv.";
          }
          container ipv6-interface-addr {
            leaf ipv6-int-addr {
              type inet:ipv6-address;
              description
                "IPv6 address for the interface.";
            }
            description
              "IPv6 interface address sub-tlv.";
          }
          container ipv6-neighbor-addr {
            leaf ipv6-neighbor-addr {
              type inet:ipv6-address;
              description
                "IPv6 address for a neighboring router
                 on this link.";
            }
            description
              "IPv6 neighbor address sub-tlv.";
          }
          reference
            "RFC 5307 - IS-IS Extensions in Support of Generalized
             Multi-Protocol Label Switching (GMPLS)";
        }
        container srlgs {
          description
            "List of SRLGs.";
          leaf-list srlg {
            type te-types:srlg;
            description
              "SRLG value of the link.";
          }
        }
        description
          "List of application specific SRLG tlvs.";
      }
      description
        "Application specific SRLG tlv.";
    }
  }

  /* Management */

  augment "/rt:routing/"
        + "rt:control-plane-protocols/rt:control-plane-protocol"
        + "/isis:isis" {
    when "derived-from-or-self(/rt:routing"
       + "/rt:control-plane-protocols"
       + "/rt:control-plane-protocol/rt:type, 'isis:isis')" {
      description
        "This augments the IS-IS routing protocol when used";
    }
    description
      "This augments the IS-IS protocol management
       with application specific link attributes.";
    container isis-link-attr {
      container link-attr-op-mode {
        description
          "Configuration of application attribute advertisement
           and usage.";
        leaf rsvp-te-advertise {
          type attr-advertise-mode;
          description
            "Advertisement for RSVP-TE.";
          reference
            "RFC 9479: IS-IS Application-Specific Link Attributes,
             Section 3.";
        }
        leaf lfa-advertise {
          type attr-advertise-mode;
          description
            "Advertisement for Link Free Alternates (LFA). ASLA
             advertisements will be advertised and used if
             specified.";
          reference
             "RFC 9479: IS-IS Application-Specific Link Attributes,
              Section 4.3.";
        }
        leaf sr-policy-advertise {
          type attr-advertise-mode;
          description
            "Advertisement for Segment Routing Policy (SR-Policy).
             ASLA advertisements will be advertised and used if
             specified.";
          reference
            "RFC 9479: IS-IS Application-Specific Link Attributes,
             Section 4.3.";
        }
        leaf flex-algo {
          type enumeration {
            enum asla-legacy {
              value 0;
              description
                "The L-flag is set in the ALSA advertisement, and
                 legacy advertisements are used for the
                 application.";
            }
            enum app-specific {
              value 1;
              description
                "Application-specific advertisements with the L-flag
                 clear are sent and used. ";
            }
          }
          default "app-specific";
          description
            "Advertisement for Flexible Algorithm Application.";
          reference
            "RFC 9350: IGP Flexible Algorithm, Section 12.";
        }
      }
      description
        "Application specific link attributes.";
      reference
        "RFC 9479 - IS-IS Application-Specific Link Attributes";
    }
  }

  augment "/rt:routing/"
        + "rt:control-plane-protocols/rt:control-plane-protocol"
        + "/isis:isis/isis:interfaces/isis:interface" {
    when "derived-from-or-self(/rt:routing"
       + "/rt:control-plane-protocols"
       + "/rt:control-plane-protocol/rt:type, 'isis:isis')" {
      description
        "This augments the IS-IS routing protocol when used.";
    }
    description
      "This augments the IS-IS interface management
       with application specific link attributes.";
    container isis-asla {
      list interface-asla {
        key "link-attr-app";
        leaf link-attr-app {
          type iana-link-attr-apps:igp-link-attr-app;
          description
            "Application-specific attributes. Note that
             when encoded, applications with identical
             attributes may be included in the same sub-TLV.";
        }
        leaf te-metric {
          type te-types:te-metric;
          description
            "TE metric.";
          reference
            "RFC 5305: IS-IS Extensions for Traffic Engineering";
        }
        leaf admin-group {
          type te-types:admin-group;
          description
            "Administrative Group / Resource Class/Color.";
          reference
            "RFC 5305: IS-IS Extensions for Traffic Engineering";
        }
        container srlgs {
          description
            "List of SRLGs.";
          leaf-list srlg {
            type te-types:srlg;
            description
              "SRLG value of the link.";
          }
        }
        description
          "ASLA interface configuration.";
      }
      description
        "Application specific link attributes configuration.";
    }
  }

  /* TLV 22 */

  augment "/rt:routing/"
        + "rt:control-plane-protocols/rt:control-plane-protocol"
        + "/isis:isis/isis:database/isis:levels/isis:lsp"
        + "/isis:extended-is-neighbor/isis:neighbor"
        + "/isis:instances/isis:instance" {
    when "derived-from-or-self(/rt:routing"
       + "/rt:control-plane-protocols"
       + "/rt:control-plane-protocol/rt:type, 'isis:isis')" {
      description
        "This augments the IS-IS routing protocol when used";
    }
    description
      "This augments the IS-IS protocol LSDB TLV22.";
    uses application-specific-link-attributes-sub-tlv;
  }

  /* TLV 223 */

  augment "/rt:routing/"
        + "rt:control-plane-protocols/rt:control-plane-protocol"
        + "/isis:isis/isis:database/isis:levels/isis:lsp"
        + "/isis:mt-is-neighbor/isis:neighbor"
        + "/isis:instances/isis:instance" {
    when "derived-from-or-self(/rt:routing"
       + "/rt:control-plane-protocols"
       + "/rt:control-plane-protocol/rt:type, 'isis:isis')" {
      description
        "This augments the IS-IS routing protocol when used";
    }
    description
      "This augments the IS-IS protocol LSDB TLV223.";
    uses application-specific-link-attributes-sub-tlv;
  }

  /* Application-specific SRLG TLV 238 */

  augment "/rt:routing/"
        + "rt:control-plane-protocols/rt:control-plane-protocol"
        + "/isis:isis/isis:database/isis:levels/isis:lsp" {
    when "derived-from-or-self(/rt:routing"
       + "/rt:control-plane-protocols"
       + "/rt:control-plane-protocol/rt:type, 'isis:isis')" {
      description
        "This augments the IS-IS routing protocol when used";
    }
    description
      "This augments the IS-IS protocol LSDB.";
    uses application-specific-srlg-tlv;
  }
}
